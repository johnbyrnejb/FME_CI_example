FME workspace ci_example.fmw

Parameters:
- DestDataset_ESRISHAPE = /home/byrnejo/temp/output   # Destination Esri Shapefile Folder
- Generalise = 100   # Generalization Tolerance
- county_selector = BNF   # County
- SourceDataset_ESRISHAPE = /home/byrnejo/temp/output/business_products.ros_registration_counties.shp   # Source Esri Shapefile(s)

Readers:
- ESRISHAPE_2: ESRISHAPE from $(SourceDataset_ESRISHAPE)

Writers:
- ESRISHAPE_1: ESRISHAPE to $(DestDataset_ESRISHAPE)

business_products.ros_registration_counties (reader ESRISHAPE_2)
    attributes: objectid number(20,0), county char(50), county2 char(5)
    -> Generalizer
Note: Generalizer with a published parameter to allow the user to input a tolerance value
Generalizer
    ALG_TEXT = Douglas (Generalize)
    PRESERVE = No
    PRESERVE_PATHS = No
    TOLERANCE = $(Generalise)
    -> Tester
Tester
    BOOL_OP = OR
    COMPOSITE_TEST = 1
    TEST_CLAUSE = TEST @Value(county2) = $(county_selector)
    TEST_MODE = TEST
    PASSED -> business_products.ros_registration_counties (writer ESRISHAPE_1)
    FAILED -> Non_exported_counties
business_products.ros_registration_counties (writer ESRISHAPE_1)
    attributes: objectid number(20,0), county char(50), county2 char(5)
Non_exported_counties: Logger
    LOG_FEATURE = LOG_ONLY
    MAXCOORDS = 20
    MAXFEATS = 20
    MESSAGE = These counties were not exported: @Value(county)
    SEVERITY = INFO
